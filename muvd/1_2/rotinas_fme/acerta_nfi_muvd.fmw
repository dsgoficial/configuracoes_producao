FME workspace acerta_nfi_muvd.fmw

Parameters:
- SourceDataset_POSTGIS = bo_guayaramerin_5k_4326_utrd1   # Database
- FEATURE_TYPES = muvd.aer_al351_a muvd.aer_al510_p muvd.aer_aq060_a muvd.aer_aq110_p muvd.aer_gb005_a muvd.aer_gb013_a muvd.aer_gb013_p muvd.aer_gb015_a muvd.aer_gb025_a muvd.aer_gb025_l muvd.aer_gb030_a muvd.aer_gb030_p muvd.aer_gb035_a muvd.aer_gb040_a muvd.aer_gb040_p muvd.aer_gb045_a muvd.aer_gb055_a muvd.aer_gb065_a muvd.aer_gb070_a muvd.aer_gb075_a muvd.aer_gb230_a muvd.aer_gb250_a muvd.aernav_ga033_a muvd.aernav_ga033_p muvd.aernav_ga036_p muvd.aernav_ga037_p muvd.aernav_gb485_a muvd.aernav_gb485_l muvd.agr_aj030_a muvd.agr_aj050_a muvd.agr_aj060_a muvd.agr_aj085_a muvd.agr_aj110_a muvd.agr_al270_a muvd.agr_am020_a muvd.agr_am030_a muvd.agr_bh051_a muvd.agr_ea010_a muvd.agr_ea020_l muvd.agr_ea030_a muvd.agr_ea040_a muvd.agr_ea050_a muvd.agr_ea055_a muvd.agr_ea060_a muvd.aux_insumo_externo_a muvd.aux_insumo_externo_l muvd.aux_insumo_externo_p muvd.aux_moldura_a muvd.aux_revisao_a muvd.aux_revisao_l muvd.aux_revisao_p muvd.aux_validacao_l muvd.aux_validacao_p muvd.bound_fa000_l muvd.bound_fa002_a muvd.bound_fa003_a muvd.bound_fa012_a muvd.bound_fa210_a muvd.bound_zb030_p muvd.centroide_al020_p muvd.centroide_ba040_p muvd.centroide_bh010_p muvd.centroide_bh015_p muvd.centroide_bh020_p muvd.centroide_bh030_p muvd.centroide_bh082_p muvd.centroide_bh090_p muvd.centroide_bh120_p muvd.centroide_bh135_p muvd.centroide_bh140_p muvd.centroide_bh150_p muvd.centroide_bh160_p muvd.centroide_bj030_p muvd.centroide_bj060_p muvd.centroide_bj099_p muvd.centroide_bj100_p muvd.centroide_da005_p muvd.centroide_da010_p muvd.centroide_db170_p muvd.centroide_ea010_p muvd.centroide_ea040_p muvd.centroide_ea050_p muvd.centroide_ea055_p muvd.centroide_eb010_p muvd.centroide_eb020_p muvd.centroide_ec015_p muvd.centroide_ed010_p muvd.centroide_ed020_p muvd.centroide_zd020_p muvd.cul_aa010_a muvd.cul_aa011_l muvd.cul_aa020_a muvd.cul_aa020_p muvd.cul_aa040_a muvd.cul_aa040_p muvd.cul_aa052_a muvd.cul_aa054_p muvd.cul_ab000_a muvd.cul_ab010_a muvd.cul_ab040_a muvd.cul_ac010_a muvd.cul_ac020_a muvd.cul_ac030_a muvd.cul_ac040_a muvd.cul_ac060_a muvd.cul_ac507_a muvd.cul_ad010_a muvd.cul_ad020_a muvd.cul_ad020_p muvd.cul_ad025_a muvd.cul_ad030_a muvd.cul_ad030_p muvd.cul_ad041_a muvd.cul_ad050_a muvd.cul_ad055_a muvd.cul_ad060_a muvd.cul_af010_p muvd.cul_af020_l muvd.cul_af030_a muvd.cul_af040_a muvd.cul_af040_l muvd.cul_af040_p muvd.cul_af050_a muvd.cul_af050_l muvd.cul_af050_p muvd.cul_af070_p muvd.cul_af080_a muvd.cul_af080_p muvd.cul_ag030_a muvd.cul_ag040_a muvd.cul_ag060_a muvd.cul_ah070_a muvd.cul_ah070_p muvd.cul_aj051_p muvd.cul_aj055_a muvd.cul_ak015_a muvd.cul_ak020_a muvd.cul_ak020_l muvd.cul_ak020_p muvd.cul_ak030_a muvd.cul_ak040_a muvd.cul_ak060_a muvd.cul_ak070_a muvd.cul_ak080_l muvd.cul_ak100_a muvd.cul_ak101_a muvd.cul_ak110_a muvd.cul_ak120_a muvd.cul_ak121_p muvd.cul_ak130_a muvd.cul_ak130_l muvd.cul_ak150_l muvd.cul_ak160_a muvd.cul_ak164_a muvd.cul_ak170_a muvd.cul_ak180_a muvd.cul_al010_a muvd.cul_al012_a muvd.cul_al013_a muvd.cul_al014_a muvd.cul_al014_l muvd.cul_al014_p muvd.cul_al018_a muvd.cul_al018_l muvd.cul_al018_p muvd.cul_al019_a muvd.cul_al025_p muvd.cul_al030_a muvd.cul_al035_p muvd.cul_al036_a muvd.cul_al036_p muvd.cul_al037_a muvd.cul_al037_p muvd.cul_al050_l muvd.cul_al070_l muvd.cul_al073_p muvd.cul_al080_l muvd.cul_al099_a muvd.cul_al099_p muvd.cul_al110_l muvd.cul_al110_p muvd.cul_al131_a muvd.cul_al131_l muvd.cul_al131_p muvd.cul_al140_a muvd.cul_al142_a muvd.cul_al155_a muvd.cul_al155_l muvd.cul_al155_p muvd.cul_al170_a muvd.cul_al200_a muvd.cul_al241_a muvd.cul_al241_p muvd.cul_al250_a muvd.cul_al250_p muvd.cul_al260_l muvd.cul_am010_a muvd.cul_am011_a muvd.cul_am040_a muvd.cul_am065_a muvd.cul_am070_a muvd.cul_am071_a muvd.cul_am075_a muvd.cul_am080_a muvd.cul_am080_p muvd.cul_aq140_a muvd.cul_aq141_a muvd.cul_aq150_a muvd.cul_aq150_l muvd.cul_at005_l muvd.cul_at010_a muvd.cul_at010_p muvd.cul_at011_a muvd.cul_at011_p muvd.cul_at012_a muvd.cul_at041_l muvd.cul_at042_l muvd.cul_at042_p muvd.cul_at045_a muvd.cul_bh040_a muvd.cul_bh075_a muvd.cul_bh075_p muvd.cul_bh155_a muvd.cul_bh220_a muvd.cul_bi010_a muvd.cul_bi010_p muvd.cul_ea031_a muvd.cul_fa015_a muvd.cul_fa100_a muvd.cul_fa165_a muvd.cul_fa220_a muvd.delimitador_area_construida_l muvd.delimitador_elemento_hidrografico_l muvd.delimitador_massa_dagua_l muvd.delimitador_vegetacao_l muvd.elev_ca010_l muvd.elev_ca030_p muvd.fou_zd019_a muvd.fou_zd019_l muvd.fou_zd019_p muvd.fou_zd020_a muvd.fou_zd050_l muvd.fou_zd050_p muvd.geo_fa091_l muvd.hyd_bd100_p muvd.hyd_bd123_l muvd.hyd_bh010_a muvd.hyd_bh010_l muvd.hyd_bh012_p muvd.hyd_bh030_a muvd.hyd_bh030_l muvd.hyd_bh065_a muvd.hyd_bh065_l muvd.hyd_bh082_a muvd.hyd_bh090_a muvd.hyd_bh100_a muvd.hyd_bh100_l muvd.hyd_bh120_a muvd.hyd_bh120_l muvd.hyd_bh135_a muvd.hyd_bh140_a muvd.hyd_bh140_l muvd.hyd_bh145_p muvd.hyd_bh165_a muvd.hyd_bh165_l muvd.hyd_bh165_p muvd.hyd_bh172_p muvd.hyd_bh180_l muvd.hyd_bh180_p muvd.hyd_bh230_a muvd.hyd_bh230_p muvd.hyd_bi006_a muvd.hyd_bi020_a muvd.hyd_bi030_a muvd.hyd_bi030_l muvd.hyd_bi040_l muvd.hyd_bi044_a muvd.hyd_bi044_l muvd.hyd_bi050_a muvd.hyd_bi050_p muvd.hydnav_bc050_a muvd.hydnav_bc070_a muvd.mil_ah050_a muvd.mil_ah050_l muvd.mil_ah050_p muvd.mil_ah060_a muvd.mil_ah060_p muvd.mil_al065_a muvd.mil_al120_a muvd.mil_al121_a muvd.mil_am060_a muvd.mil_su001_a muvd.oce_ba040_a muvd.oce_bb081_a muvd.oce_bb081_l muvd.oce_bb110_a muvd.oce_bb110_l muvd.oce_bd115_a muvd.oce_bd115_p muvd.oce_bd120_a muvd.oce_bd120_l muvd.oce_bd130_a muvd.oce_bd130_p muvd.oce_bd180_p muvd.oce_bd181_a muvd.oce_bh050_a muvd.oce_bh190_a muvd.phy_ba010_l muvd.phy_ba030_a muvd.phy_ba050_a muvd.phy_bh150_a muvd.phy_bh160_a muvd.phy_bj020_a muvd.phy_bj030_a muvd.phy_bj031_a muvd.phy_bj031_l muvd.phy_bj040_l muvd.phy_bj060_a muvd.phy_bj060_p muvd.phy_bj065_a muvd.phy_bj065_p muvd.phy_bj099_a muvd.phy_bj100_a muvd.phy_da005_a muvd.phy_da010_a muvd.phy_db010_l muvd.phy_db029_p muvd.phy_db061_a muvd.phy_db061_l muvd.phy_db070_l muvd.phy_db071_l muvd.phy_db090_a muvd.phy_db090_l muvd.phy_db100_l muvd.phy_db110_l muvd.phy_db115_a muvd.phy_db115_p muvd.phy_db150_p muvd.phy_db160_a muvd.phy_db170_a muvd.phy_db180_a muvd.phy_db180_p muvd.phy_ec020_a muvd.pop_ai030_a muvd.pop_ai030_p muvd.pop_ai040_a muvd.pop_al020_a muvd.pop_al022_a muvd.port_bb005_a muvd.port_bb009_a muvd.port_bb030_l muvd.port_bb030_p muvd.port_bb082_a muvd.port_bb082_l muvd.port_bb090_a muvd.port_bb199_a muvd.port_bb241_a muvd.tran_al165_p muvd.tran_al211_a muvd.tran_al211_l muvd.tran_an010_l muvd.tran_an050_l muvd.tran_an060_a muvd.tran_an075_a muvd.tran_an076_a muvd.tran_an077_a muvd.tran_an078_a muvd.tran_ap040_l muvd.tran_ap041_l muvd.tran_ap075_l muvd.tran_aq040_a muvd.tran_aq040_l muvd.tran_aq055_a muvd.tran_aq055_p muvd.tran_aq056_a muvd.tran_aq056_p muvd.tran_aq063_a muvd.tran_aq063_l muvd.tran_aq065_l muvd.tran_aq068_a muvd.tran_aq068_l muvd.tran_aq068_p muvd.tran_aq070_l muvd.tran_aq080_a muvd.tran_aq095_p muvd.tran_aq113_l muvd.tran_aq116_a muvd.tran_aq116_p muvd.tran_aq125_a muvd.tran_aq130_a muvd.tran_aq130_l muvd.tran_aq135_a muvd.tran_aq151_a muvd.tran_aq151_l muvd.tran_aq170_a muvd.tran_aq180_a muvd.tran_aq210_a muvd.tran_aq210_p muvd.tran_bh020_a muvd.tran_bh020_l muvd.tran_bh070_l muvd.tran_bh070_p muvd.tran_bh110_l muvd.tran_bi005_a muvd.tran_bi045_l muvd.tran_bi045_p muvd.veg_bh015_a muvd.veg_bj110_a muvd.veg_eb010_a muvd.veg_eb020_a muvd.veg_ec005_p muvd.veg_ec015_a muvd.veg_ec015_l muvd.veg_ec040_a muvd.veg_ed010_a muvd.veg_ed020_a
- nome_bloco = W06521S1049   # Nome do Bloco
- DestDataset_POSTGIS = bo_guayaramerin_5k_4326_utrd1   # Connection

Readers:
- POSTGIS_1: POSTGIS from $(SourceDataset_POSTGIS)

Writers:
- POSTGIS_2: POSTGIS to $(DestDataset_POSTGIS)

aer_al351_a (reader POSTGIS_1)
    attributes: id uuid, acc int4, adr varchar(255), caa int4, ccn varchar(255), cud varchar(255), dsc varchar(255), ela int4, fna varchar(255), nfi varchar(255), oth varchar(255), pcf int4, sdp varchar(255), ssd varchar(255), stc int4, ufi varchar(255), uui varchar(255), ANNOTATION text, ATTRSCHEMA text, CODE1 varchar(5), CODE2 varchar(5), COND_NUM int8, COR_DATE date, COR_TECH text, C_COMMENTS text, ERRTYPE varchar(255), INSTANCE int2, LABEL1 text, LABEL2 text, MAGNITUDE float8,
      ORIG_FID int8, ORIG_GEOM text, ORIG_TABLE text, RETAINIGN text, UUI text, VER_DATE date, VER_TECH text, V_COMMENTS text, ama int4, apm int4, apt int4, apy int4, aqf int4, asu int4, asx int4, asy int4, atb int4, atc int4, awp int4, bac int4, bat int4, bcc int4, bgt int4, bloco varchar(255), bmc int4, bnf int4, boc int4, bot int4, bsc int4, bsm int4,
      bst int4, bsu int4, ca2 int4, cab int4, cam int4, cat int4, ccg int4, cct int4, cda int4, cet int4, cmo float4, cob int4, corrigido int4, cra int4, crm int4, csd float4, cso int4, csp int4, ctc int4, cvt int4, data_atualizacao timestamptz, data_criacao timestamptz, descricao varchar(255), dev int4, dft int4, dfu int4, dgc int4, dit int4, dmb float4, dmt float4,
      dpr int4, dsd int4, dsp int4, dzc int4, dzp float4, esc int4, fac int4, fbt int4, fco int4, fcs int4, fef int4, fer int4, ffa int4, ffn int4, ffn_2 int4, ffp int4, fhc int4, fic int4, flo int4, fmm int4, fon int4, fonte varchar(255), fot int4, fpt int4, frt int4, fti int4, fuc int4, gaw float4, gfy int4, got int4,
      gtc int4, gug int4, haf int4, hca float4, hgd int4, hgt float4, hlk int4, hqc int4, hst int4, htp int4, hyp int4, iko varchar(255), inu int4, irg int4, iwt int4, justificativa varchar(255), lnu float4, loc int4, ltn int4, lun int4, lzn float4, man int4, mcc int4, mel int4, mes int4, mfe int4, mi varchar(255), mmo int4, mst int4, mte int4,
      mzn int4, na8 varchar(255), nln float4, nlt int4, nmi int4, nome varchar(255), nos int4, npl int4, nvs int4, nwd float4, obs varchar(255), observacao varchar(255), ocs int4, ohc float4, one int4, ooc int4, opc int4, operador_atualizacao varchar(255), operador_criacao varchar(255), opm int4, oss int4, owo int4, pby int4, plt int4, pos int4, ppa int4, ppo int4, ppo_2 int4, prm int4, prw int4,
      pth int4, pwc int4, pyc int4, rac int4, ras int4, ray int4, rel int4, rfa int4, rfd int4, rgc int4, rid varchar(255), rir int4, rkf int4, rls int4, rmw float4, rod float4, ror int4, rra int4, rrc int4, rsa int4, rst int4, rta int4, rwc int4, sad int4, sbt int4, scc int4, sdo float4, sdt int4, sfs int4, shd int4,
      sic int4, slr int4, slt int4, smc int4, spt int4, srd int4, ssc int4, ssr int4, stp int4, subfase_id int4, swc int4, tcs int4, tel int4, tft int4, thl int4, tid int4, tme int4, tos int4, tra int4, tre int4, trh float4, trp int4, trt int4, tsm int4, ttc int4, tty int4, tuc int4, txp int4, ubc float4, uma int4,
      unm int4, vca int4, veg int4, vgp int4, vgt int4, voa int4, voi varchar(255), vsp int4, wcc int4, wd1 float4, wd2 float4, wd5 float4, wdu float4, weq int4, wft int4, wid float4, wit int4, wle int4, wlo int4, wor int4, wpi int4, wrx int4, ws0 int4, wsi int4, wst int4, wti int4, ysu int4, ywq int4, zva float4, zvh float4
    -> Tester
Tester
    BOOL_OP = AND
    TEST_CLAUSE:
      TEST fna ATTRIBUTE_HAS_A_VALUE ""
      TEST @Value(fna) NOT_= AOI
    TEST_MODE = TEST
    PASSED -> Tester_2
Tester_2
    BOOL_OP = OR
    TEST_CLAUSE = TEST nfi ATTRIBUTE_HAS_A_VALUE ""
    TEST_MODE = TEST
    FAILED -> Tester_8
Tester_8
    BOOL_OP = OR
    TEST_CLAUSE:
      TEST fna ATTRIBUTE_IS_MISSING ""
      TEST nfi ATTRIBUTE_IS_MISSING ""
    TEST_MODE = TEST
    FAILED -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_3
AttributeCreator_3
    ATTR_TABLE = SET_TO fcode = @Left(@UpperCase(@Right(@Value(fme_feature_type),7)),5)
    -> Tester_9
Tester_9
    BOOL_OP = COMPOSITE
    COMPOSITE_TEST = 1 AND 2
    TEST_CLAUSE:
      TEST fna NOT_ATTRIBUTE_VALUE_NULL ""
      TEST @Value(fna) != UNK
    TEST_MODE = TEST
    PASSED -> Tester_3
Tester_3
    BOOL_OP = OR
    TEST_CLAUSE = TEST @Value(nfi) TYPE NUM
    TEST_MODE = TEST
    FAILED -> Tester_6
Tester_6
    BOOL_OP = OR
    TEST_CLAUSE = TEST @Value(fcode) = ZD040
    TEST_MODE = TEST
    PASSED -> AttributeKeeper_2
    PASSED -> AttributeRemover
    FAILED -> Aggregator_2
    FAILED -> AttributeRemover_2
Aggregator_2
    ACCUM_ATTRS_NAME = Use Attributes From One Feature
    AGGREGATE_TYPE = Heterogeneous Collection
    GROUP_BY = fna
    MODE = Geometry - Assemble One Level
    SEP = ,
    AGGREGATE -> AttributeKeeper_2
AttributeKeeper_2
    CREATE_BULK_MODE_FEATURES = NO
    KEEP_ATTRS = fcode,fna,id
    -> GeometryRemover_2
GeometryRemover_2
    -> Sorter
Sorter
    SORT_PARM = fna ALPHA ASCENDING
    SORTED -> Counter
Counter
    CNT_ATTR = _count
    DOMAIN = counter
    SCOPE = Global
    START = 1
    -> AttributeCreator
AttributeCreator
    ATTR_TABLE = SET_TO nfi = BRA$(nome_bloco)_@Format(%03s,@Value(_count))
    -> Tester_10
Tester_10
    BOOL_OP = OR
    TEST_CLAUSE = TEST @Value(fcode) = ZD040
    TEST_MODE = TEST
    PASSED -> FeatureMerger_4 [SUPPLIER]
    FAILED -> FeatureMerger_5 [SUPPLIER]
AttributeRemover
    REMOVE_ATTRS = nfi
    -> FeatureMerger_4 [REQUESTOR]
FeatureMerger_4
    ATTR_ACCUM_MODE = Merge Supplier
    ATTR_CONFLICT_RES = Use Requestor
    IGNORE_NULLS = No
    JOIN_KEYS = @Value(fna) @Value(fna) AUTO @Value(id) @Value(id) AUTO
    MERGE_TYPE = Attributes Only
    PROCESS_DUPS = NO
    REJECT_NULL_MISSING_KEYS = No
    SUPPLIERS_FIRST = No
    MERGED -> Junction
AttributeRemover_2
    REMOVE_ATTRS = nfi
    -> FeatureMerger_5 [REQUESTOR]
FeatureMerger_5
    ATTR_ACCUM_MODE = Merge Supplier
    ATTR_CONFLICT_RES = Use Requestor
    IGNORE_NULLS = No
    JOIN_KEYS = @Value(fna) @Value(fna) AUTO
    MERGE_TYPE = Attributes Only
    PROCESS_DUPS = NO
    REJECT_NULL_MISSING_KEYS = No
    SUPPLIERS_FIRST = No
    MERGED -> Junction
Junction
    -> Counter_2
Counter_2
    CNT_ATTR = _count2
    DOMAIN = counter
    SCOPE = Global
    START = 0
    -> Aggregator
Aggregator
    ACCUM_ATTRS_NAME = Use Attributes From One Feature
    AGGREGATE_TYPE = Homogeneous Collection (If Possible)
    GROUP_BY = _count2
    MODE = Geometry - Assemble One Level
    SEP = ,
    AGGREGATE -> Table1 (writer POSTGIS_2)
Table1 (writer POSTGIS_2)
