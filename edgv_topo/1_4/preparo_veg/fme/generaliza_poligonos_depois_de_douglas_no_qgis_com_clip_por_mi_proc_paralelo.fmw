FME workspace generaliza_poligonos_depois_de_douglas_no_qgis_com_clip_por_mi_proc_paralelo.fmw

Parameters:
- DestDataset_SHAPEFILE = D:\borba\veg_teste\rs_50k_2025\resto   # Destination Esri Shapefile Folder
- SourceDataset_OGCGEOPACKAGE_3 = D:\borba\veg_teste\rs_50k_2025\resto\poligonos_generalizados.gpkg   # GeoPackage File
- SourceDataset_OGCGEOPACKAGE = D:\borba\download_planet_conv_rs\molduras_download_pit_ia.gpkg   # GeoPackage File

Readers:
- OGCGEOPACKAGE_2: OGCGEOPACKAGE from $(SourceDataset_OGCGEOPACKAGE_3)
- OGCGEOPACKAGE_1: OGCGEOPACKAGE from $(SourceDataset_OGCGEOPACKAGE)

Writers:
- SHAPEFILE_1: SHAPEFILE to $(DestDataset_SHAPEFILE)

poligonos_generalizados (reader OGCGEOPACKAGE_2)
    attributes: cat mediumint, DN mediumint, fid int,PrimaryKey
    -> Clipper [CANDIDATE]
molduras (reader OGCGEOPACKAGE_1)
    attributes: inom text, mi text, fid int,PrimaryKey
    -> Reprojector
Reprojector
    DEST = SIRGAS2000.UTM-22S
    INTERPOLATION_TYPE_NAME = Nearest Neighbor
    RASTER_CELL_SIZE = Preserve Cells
    RASTER_TOLERANCE = 0.0
    REPROJECTED -> Tiler
Tiler
    CLEANING_TOLERANCE = Automatic
    COLUMN_ATTR = _column
    DUPLICATE_ON_TILE_BORDERS = NO
    GROUP_BY = mi
    INVALID_PART_HANDLING = REJECT_WHOLE_FEATURE
    MISSING_MEASURE_VALUES = Linear Interpolation
    MISSING_Z_VALUES = Planar Interpolation
    NUM_HORIZONTAL_TILES = 2
    NUM_VERTICAL_TILES = 2
    ROW_ATTR = _row
    STARTINGCORNER = BOTTOM_LEFT
    TILING_TYPE = NUM_TILES
    TILED -> AttributeCreator
AttributeCreator
    ATTR_TABLE = SET_TO _identifier (varchar(200)) = @Value(mi)_@Value(_row)_@Value(_column)
    -> Bufferer
    -> Reprojector_3
Bufferer
    ANGLE = 22.5
    CAP_STYLE = Square
    CORNER_STYLE = Miter
    MITER_LIMIT = 1
    MODE = AREA
    OFFSET = 100
    OFFSET_UNITS = NONE
    PRECISION = APPROX
    BUFFERED -> Clipper [CLIPPER]
Clipper
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Tester
Tester
    BOOL_OP = OR
    TEST_CLAUSE = TEST DN NOT_ATTRIBUTE_VALUE_NULL ""
    TEST_MODE = TEST
    PASSED -> Sorter
Sorter
    SORT_PARM = _identifier NATURAL ASCENDING
    SORTED -> Densifier
Densifier
    INTERVAL = 1
    MODE = Uniform Interval
    DENSIFIED -> Generalizer
Generalizer
    ALG_TEXT = NURBfit (Smooth)
    CLEANING_TOLERANCE = Automatic
    DEGREE = 2
    GROUP_BY = _identifier
    PRESERVE = Yes
    PRESERVE_PATHS = No
    SEGMENT_LENGTH = 0
    -> Generalizer_2
Generalizer_2
    ALG_TEXT = Douglas (Generalize)
    CLEANING_TOLERANCE = Automatic
    GROUP_BY = _identifier
    PRESERVE = Yes
    PRESERVE_PATHS = No
    TOLERANCE = 2
    -> Generalizer_3
Generalizer_3
    ALG_TEXT = NURBfit (Smooth)
    CLEANING_TOLERANCE = Automatic
    DEGREE = 2
    GROUP_BY = _identifier
    PRESERVE = Yes
    PRESERVE_PATHS = No
    SEGMENT_LENGTH = 0
    -> Generalizer_4
Generalizer_4
    ALG_TEXT = Douglas (Generalize)
    CLEANING_TOLERANCE = Automatic
    GROUP_BY = _identifier
    PRESERVE = Yes
    PRESERVE_PATHS = No
    TOLERANCE = 1.5
    -> AreaGapAndOverlapCleaner
AreaGapAndOverlapCleaner
    CLEANING_TOLERANCE = Automatic
    CONNECT_Z_MODE = First Wins
    DEAGGREGATE_INPUT = YES
    FILL_ALL_GAPS = Yes
    GROUP_BY = _identifier
    MEASURE_TYPE = Continuous
    MISSING_VAL_MODE = Compute
    REPAIR_METHOD = Longest Boundary
    REPAIRED -> Reprojector_2
Reprojector_2
    DEST = EPSG:4674
    INTERPOLATION_TYPE_NAME = Nearest Neighbor
    RASTER_CELL_SIZE = Preserve Cells
    RASTER_TOLERANCE = 0.0
    REPROJECTED -> Clipper_2 [CANDIDATE]
Reprojector_3
    DEST = EPSG:4674
    INTERPOLATION_TYPE_NAME = Nearest Neighbor
    RASTER_CELL_SIZE = Preserve Cells
    RASTER_TOLERANCE = 0.0
    REPROJECTED -> Clipper_2 [CLIPPER]
Clipper_2
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AreaGapAndOverlapCleaner_2
AreaGapAndOverlapCleaner_2
    CLEANING_TOLERANCE = Automatic
    CONNECT_Z_MODE = First Wins
    DEAGGREGATE_INPUT = YES
    FILL_ALL_GAPS = Yes
    MEASURE_TYPE = Continuous
    MISSING_VAL_MODE = Compute
    REPAIR_METHOD = Longest Boundary
    REPAIRED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Dissolver
    REPAIRED -> Dissolver
Dissolver
    ACCUM_INPUT_ATTRS = Merge Incoming Attributes
    CLEANING_TOLERANCE = Automatic
    CONNECT_Z_MODE = First Wins
    DEAGGREGATE_INPUT = Yes
    GROUP_BY = DN mi
    AREA -> poligonos_cobter_generalizado2 (writer SHAPEFILE_1)
poligonos_cobter_generalizado2 (writer SHAPEFILE_1)
    attributes: tipo long
