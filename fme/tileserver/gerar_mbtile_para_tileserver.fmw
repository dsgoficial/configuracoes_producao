FME workspace gerar_mbtile_para_tileserver.fmw

Parameters:
- SourceDataset_GEOTIFF = ""$(FME_MF_DIR)03042023\03042023_R1C1.tif" "$(FME_MF_DIR)03042023\03042023_R1C2.tif" "$(FME_MF_DIR)03042023\03042023_R1C3.tif" "$(FME_MF_DIR)03042023\03042023_R2C1.tif" "$(FME_MF_DIR)03042023\03042023_R2C2.tif" "$(FME_MF_DIR)03042023\03042023_R2C3.tif" "$(FME_MF_DIR)03042023\03042023_R3C1.tif" "$(FME_MF_DIR)03042023\03042023_R3C2.tif" "$(FME_MF_DIR)03042023\03042023_R3C3.tif" "$(FME_MF_DIR)03042023\03042023_R4C1.tif" "$(FME_MF_DIR)03042023\03042023_R4C2.tif" "$(FME_MF_DIR)03042023\03042023_R4C3.tif" "$(FME_MF_DIR)03042023\03042023_R5C1.tif" "$(FME_MF_DIR)03042023\03042023_R5C2.tif" "$(FME_MF_DIR)03042023\03042023_R5C3.tif" "$(FME_MF_DIR)03042023\03042023_R6C1.tif" "$(FME_MF_DIR)03042023\03042023_R6C2.tif" "$(FME_MF_DIR)03042023\03042023_R6C3.tif" "$(FME_MF_DIR)03042023\03042023_R7C1.tif" "$(FME_MF_DIR)03042023\03042023_R7C2.tif" "$(FME_MF_DIR)03042023\03042023_R7C3.tif" "$(FME_MF_DIR)03042023\03042023_R8C1.tif" "$(FME_MF_DIR)03042023\03042023_R8C2.tif" "$(FME_MF_DIR)03042023\03042023_R8C3.tif""   # Source GeoTIFF File(s) or URL(s)
- SourceDataset_GEOTIFF_5 = ""$(FME_MF_DIR)07112023\07112023_R1C1.tif" "$(FME_MF_DIR)07112023\07112023_R1C2.tif" "$(FME_MF_DIR)07112023\07112023_R1C3.tif" "$(FME_MF_DIR)07112023\07112023_R2C1.tif" "$(FME_MF_DIR)07112023\07112023_R2C2.tif" "$(FME_MF_DIR)07112023\07112023_R2C3.tif" "$(FME_MF_DIR)07112023\07112023_R3C1.tif" "$(FME_MF_DIR)07112023\07112023_R3C2.tif" "$(FME_MF_DIR)07112023\07112023_R3C3.tif" "$(FME_MF_DIR)07112023\07112023_R4C1.tif" "$(FME_MF_DIR)07112023\07112023_R4C2.tif" "$(FME_MF_DIR)07112023\07112023_R4C3.tif" "$(FME_MF_DIR)07112023\07112023_R5C1.tif" "$(FME_MF_DIR)07112023\07112023_R5C2.tif" "$(FME_MF_DIR)07112023\07112023_R5C3.tif""   # Source GeoTIFF File(s) or URL(s)
- SourceDataset_GEOTIFF_7 = ""$(FME_MF_DIR)08022023\08022023_R1C1.tif" "$(FME_MF_DIR)08022023\08022023_R1C2.tif" "$(FME_MF_DIR)08022023\08022023_R1C3.tif" "$(FME_MF_DIR)08022023\08022023_R2C1.tif" "$(FME_MF_DIR)08022023\08022023_R2C2.tif" "$(FME_MF_DIR)08022023\08022023_R2C3.tif" "$(FME_MF_DIR)08022023\08022023_R3C1.tif" "$(FME_MF_DIR)08022023\08022023_R3C2.tif" "$(FME_MF_DIR)08022023\08022023_R3C3.tif" "$(FME_MF_DIR)08022023\08022023_R4C1.tif" "$(FME_MF_DIR)08022023\08022023_R4C2.tif" "$(FME_MF_DIR)08022023\08022023_R4C3.tif" "$(FME_MF_DIR)08022023\08022023_R5C1.tif" "$(FME_MF_DIR)08022023\08022023_R5C2.tif" "$(FME_MF_DIR)08022023\08022023_R5C3.tif" "$(FME_MF_DIR)08022023\08022023_R6C1.tif" "$(FME_MF_DIR)08022023\08022023_R6C2.tif" "$(FME_MF_DIR)08022023\08022023_R6C3.tif" "$(FME_MF_DIR)08022023\08022023_R7C1.tif" "$(FME_MF_DIR)08022023\08022023_R7C2.tif" "$(FME_MF_DIR)08022023\08022023_R7C3.tif" "$(FME_MF_DIR)08022023\08022023_R8C1.tif" "$(FME_MF_DIR)08022023\08022023_R8C2.tif" "$(FME_MF_DIR)08022023\08022023_R8C3.tif" "$(FME_MF_DIR)08022023\08022023_R9C1.tif" "$(FME_MF_DIR)08022023\08022023_R9C2.tif" "$(FME_MF_DIR)08022023\08022023_R9C3.tif" "$(FME_MF_DIR)08022023\08022023_R10C1.tif" "$(FME_MF_DIR)08022023\08022023_R10C2.tif" "$(FME_MF_DIR)08022023\08022023_R10C3.tif" "$(FME_MF_DIR)08022023\08022023_R11C1.tif" "$(FME_MF_DIR)08022023\08022023_R11C2.tif" "$(FME_MF_DIR)08022023\08022023_R11C3.tif""   # Source GeoTIFF File(s) or URL(s)
- SourceDataset_GEOTIFF_6 = ""$(FME_MF_DIR)21042023\21042023_R1C1.tif" "$(FME_MF_DIR)21042023\21042023_R1C2.tif" "$(FME_MF_DIR)21042023\21042023_R1C3.tif" "$(FME_MF_DIR)21042023\21042023_R2C1.tif" "$(FME_MF_DIR)21042023\21042023_R2C2.tif" "$(FME_MF_DIR)21042023\21042023_R2C3.tif" "$(FME_MF_DIR)21042023\21042023_R3C1.tif" "$(FME_MF_DIR)21042023\21042023_R3C2.tif" "$(FME_MF_DIR)21042023\21042023_R3C3.tif" "$(FME_MF_DIR)21042023\21042023_R4C1.tif" "$(FME_MF_DIR)21042023\21042023_R4C2.tif" "$(FME_MF_DIR)21042023\21042023_R4C3.tif" "$(FME_MF_DIR)21042023\21042023_R5C1.tif" "$(FME_MF_DIR)21042023\21042023_R5C2.tif" "$(FME_MF_DIR)21042023\21042023_R5C3.tif" "$(FME_MF_DIR)21042023\21042023_R6C1.tif" "$(FME_MF_DIR)21042023\21042023_R6C2.tif" "$(FME_MF_DIR)21042023\21042023_R6C3.tif" "$(FME_MF_DIR)21042023\21042023_R7C1.tif" "$(FME_MF_DIR)21042023\21042023_R7C2.tif" "$(FME_MF_DIR)21042023\21042023_R7C3.tif" "$(FME_MF_DIR)21042023\21042023_R8C1.tif" "$(FME_MF_DIR)21042023\21042023_R8C2.tif" "$(FME_MF_DIR)21042023\21042023_R8C3.tif""   # Source GeoTIFF File(s) or URL(s)
- SourceDataset_SHAPEFILE_5 = $(FME_MF_DIR)bbox_07112023.shp   # Source Esri Shapefile(s)
- SourceDataset_SHAPEFILE_7 = $(FME_MF_DIR)bbox_08022023.shp   # Source Esri Shapefile(s)
- SourceDataset_SHAPEFILE_6 = $(FME_MF_DIR)bbox_21042023.shp   # Source Esri Shapefile(s)
- SourceDataset_SHAPEFILE = $(FME_MF_DIR)bbox_03042023.shp   # Source Esri Shapefile(s)
- DestDataset_MBTILES = D:\pedromartins\Missoes\019 - TileServer   # Destination MBTiles Folder

Readers:
- GEOTIFF_1: GEOTIFF from $(SourceDataset_GEOTIFF)
- GEOTIFF_2: GEOTIFF from $(SourceDataset_GEOTIFF_5)
- GEOTIFF_3: GEOTIFF from $(SourceDataset_GEOTIFF_7)
- GEOTIFF_4: GEOTIFF from $(SourceDataset_GEOTIFF_6)
- SHAPEFILE_1: SHAPEFILE from $(SourceDataset_SHAPEFILE)
- SHAPEFILE_2: SHAPEFILE from $(SourceDataset_SHAPEFILE_5)
- SHAPEFILE_3: SHAPEFILE from $(SourceDataset_SHAPEFILE_7)
- SHAPEFILE_4: SHAPEFILE from $(SourceDataset_SHAPEFILE_6)

Writers:
- MBTILES_1: MBTILES to $(DestDataset_MBTILES)

RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    <REJECTED> -> RasterInterpretationCoercer
RasterInterpretationCoercer
    COLOR_TO_COLOR = Scale by data type
    FLOAT_TO_INTEGER = Round
    INTERPRETATION = RGBA32
    NUMERIC_TO_COLOR = Scale by data values
    RGB_TO_RGBA = Create alpha band from nodata
    -> AttributeCreator
AttributeCreator
    ATTR_TABLE = SET_TO ordem (uint64) = 1
    -> Clipper [CANDIDATE]
bbox_07112023 (reader SHAPEFILE_2)
    attributes: bbox_07_ID varchar(5)
    -> Clipper_2 [CLIPPER]
GEOTIFF (reader GEOTIFF_2)
    -> RasterMosaicker_2
Note: Moisaicar as imagens, observar as configurações.
RasterMosaicker_2
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> AttributeCreator_2
AttributeCreator_2
    ATTR_TABLE = SET_TO ordem (uint64) = 2
    -> Clipper_2 [CANDIDATE]
bbox_08022023 (reader SHAPEFILE_3)
    attributes: bbox_08_ID varchar(5)
    -> Clipper_3 [CLIPPER]
GEOTIFF (reader GEOTIFF_3)
    -> RasterMosaicker_3
RasterMosaicker_3
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> AttributeCreator_3
Note: Criar o atributo para ordenar o mosaico final.
AttributeCreator_3
    ATTR_TABLE = SET_TO ordem (uint64) = 3
    -> Clipper_3 [CANDIDATE]
bbox_21042023 (reader SHAPEFILE_4)
    attributes: bbox_21_ID varchar(5)
    -> Clipper_4 [CLIPPER]
GEOTIFF (reader GEOTIFF_4)
    -> RasterMosaicker_4
RasterMosaicker_4
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> AttributeCreator_4
AttributeCreator_4
    ATTR_TABLE = SET_TO ordem (uint64) = 4
    -> Clipper_4 [CANDIDATE]
Note: Ordenar para mosaicar posteriormente na ordem correta.
Sorter
    SORT_PARM = ordem NATURAL ASCENDING
    SORTED -> RasterMosaicker_5
Note: Exportar como MBTiles.
CI_SantaMaria (writer MBTILES_1)

Bookmark: Imagens e Bouding Box
bbox_03042023 (reader SHAPEFILE_1)
    attributes: bbox__ID varchar(5)
    -> Clipper [CLIPPER]
GEOTIFF (reader GEOTIFF_1)
    -> RasterMosaicker

Bookmark: Clipar usando o Bounding Box e as imagens mosaicadas.
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Sorter
Clipper_2
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Sorter
Clipper_3
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Sorter
Clipper_4
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Sorter

Bookmark: Mosaicar e reprojetar
RasterMosaicker_5
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Reprojector
Note: Para o TileServer, tem que ser 3857.
Reprojector
    DEST = EPSG:3857
    INTERPOLATION_TYPE_NAME = Nearest Neighbor
    RASTER_CELL_SIZE = Preserve Cells
    RASTER_TOLERANCE = 0.0
    REPROJECTED -> CI_SantaMaria (writer MBTILES_1)
